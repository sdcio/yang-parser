module string-fail-bad-esc-seq {
	namespace "urn:vyatta.com:mgmt:string-fail-bad-esc-seq";
	prefix string-fail-bad-esc-seq;

	organization "AT&T Inc.";

	contact
		"AT&T
		 Postal: 208 S. Akard Street
		         Dallas, TX 75202
		 Web: www.att.com \* ";

	revision 2015-03-09 {
		description "Initial revision."{testPrefix:testUnknown;}
	}
}
