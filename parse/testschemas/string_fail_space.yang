module string-fail-space {
	namespace "urn:vyatta.com:mgmt:string-fail-space";
	prefix string-fail-space;

	organization "Brocade Communications Systems, Inc.";
	contact
		"Brocade Communications Systems, Inc.
		 Postal: 130 Holger Way
			 San Jose, CA 95134
		 E-mail: support@Brocade.com
		 Web: www.brocade.com";

	revision 2015-03-09 {
		description "Initial revision.";
	}

	container testcontainer {
		leaf testleaf {
			type boo lean;
			default "true";

		}
	}
}
