module string-fail-dangling-plus {
	namespace "urn:vyatta.com:mgmt:string-fail-dangling-plus";
	prefix string-fail-dangling-plus;

	organization "AT&T Inc.";
	contact
		"AT&T
		 Postal: 208 S. Akard Street
		         Dallas, TX 75202
		 Web: www.att.com" + "Dangling Plus" +;

	revision 2015-03-09 {
		description "Initial revision.";
	}

}
