module string_fail_miss_semicolon {
	namespace "urn:vyatta.com:mgmt:string_fail_miss_semicolon";
	prefix string_fail_miss_semicolon;

	organization "AT&T Inc.";
	contact
		"AT&T
		 Postal: 208 S. Akard Street
		         Dallas, TX 75202
		 Web: www.att.com"

	revision 2015-03-09 {
		description "Initial revision.";
	}
}
