module string-fail-miss-plus {
	namespace "urn:vyatta.com:mgmt:string-fail-miss-plus";
	prefix string-fail-miss-plus;

	organization "Brocade Communications Systems, Inc.";
	contact
		"Brocade Communications Systems, Inc.
		 Postal: 130 Holger Way
			 San Jose, CA 95134
		 E-mail: support@Brocade.com
		 Web: www.brocade.com\n" "missing plus";
// There is a missing plus in the above ^
	revision 2015-03-09 {
		description "Initial revision.";
	}

}
