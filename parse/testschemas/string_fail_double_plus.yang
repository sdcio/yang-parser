module string-fail-double-plus {
	namespace "urn:vyatta.com:mgmt:string-fail-double-plus";
	prefix string-fail-double-plus;

	organization "Brocade Communications Systems, Inc.";
	contact
		"Brocade Communications Systems, Inc.
		 Postal: 130 Holger Way
			 San Jose, CA 95134
		 E-mail: support@Brocade.com
		 Web: www.brocade.com\n" + 
		"Some additional test data" + + "missing plus";

	revision 2015-03-09 {
		description "Initial revision.";
	}

}
