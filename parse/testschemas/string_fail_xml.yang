module string-fail-xml {
	namespace "urn:vyatta.com:mgmt:string-fail-xml";
	prefix string-fail-xml;

	organization "Brocade Communications Systems, Inc.";
	contact
		"Brocade Communications Systems, Inc.
		 Postal: 130 Holger Way
			 San Jose, CA 95134
		 E-mail: support@Brocade.com
		 Web: www.brocade.com";

	revision 2015-03-09 {
		description "Initial revision.";
	}

// An identifier is not allowed to start (('X'/'x')('M'/'m')('L'/'l'))
	container XmLtestcontainer {
		leaf testleaf {
			type boolean;
			default "true";

		}
	}
}
