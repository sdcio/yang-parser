module string-fail-quotes {
	namespace "urn:vyatta.com:mgmt:string-fail-quotes";
	prefix string-fail-quotes;

	organization "AT&T Inc.";
	contact
		"AT&T
		 Postal: 208 S. Akard Street
		         Dallas, TX 75202
		 Web: www.att.com" +
		"Some additional test data" + nonQuoteString;
	revision 2015-03-09 {
		description "Initial revision.";
	}
}
